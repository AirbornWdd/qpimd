GNOME-PRODUCT-KROUTE-MIB DEFINITIONS ::= BEGIN

IMPORTS
	MODULE-IDENTITY,
	OBJECT-IDENTITY
		FROM SNMPv2-SMI
	gnomeProducts
		FROM GNOME-SMI;

kroute MODULE-IDENTITY
	LAST-UPDATED "200004250000Z"
	ORGANIZATION "GNOME project"
	CONTACT-INFO
		"GNU Network Object Model Environment project
		
		see http://www.gnome.org for contact persons of a particular
		area or subproject of GNOME.

		Administrative contact for MIB module:

		Jochen Friedrich
		Wingertstr. 70/1
		68809 Neulussheim
		Germany 

		email: snmp@gnome.org"
	DESCRIPTION
		"The product registrations for the various kroute subdeamons.
		These registrations are guaranteed to be unique and are used
		for SMUX registration by default (if not overridden manually)."
	::= { gnomeProducts 2 }

zserv OBJECT-IDENTITY
	STATUS  current
	DESCRIPTION
		"zserv is part of the kroute project which again is a GNU
		endorsed internet routing program.
		zserv is the main kroute process which implements routing
		entries with the kernel and handles routing updates between
		other routing protocols."
	::= { kroute 1 }

bgpd OBJECT-IDENTITY
	STATUS  current
	DESCRIPTION
		"bgpd is part of the kroute project which again is a GNU
		endorsed internet routing program."
	::= { kroute 2 }

ripd OBJECT-IDENTITY
	STATUS  current
	DESCRIPTION
		"ripd is part of the kroute project which again is a GNU
		endorsed internet routing program."
	::= { kroute 3 }

ripngd OBJECT-IDENTITY
	STATUS  current
	DESCRIPTION
		"ripngd is part of the kroute project which again is a GNU
		endorsed internet routing program."
	::= { kroute 4 }

ospfd OBJECT-IDENTITY
	STATUS  current
	DESCRIPTION
		"ospfd is part of the kroute project which again is a GNU
		endorsed internet routing program."
	::= { kroute 5 }

ospf6d OBJECT-IDENTITY
	STATUS  current
	DESCRIPTION
		"ospf6d is part of the kroute project which again is a GNU
		endorsed internet routing program."
	::= { kroute 6 }

END
